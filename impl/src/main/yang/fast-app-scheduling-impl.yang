module fast-app-scheduling-impl {
    yang-version 1;
    namespace "urn:fast:app:scheduling:impl";
    prefix "fast-app-scheduling-impl";

    import config {
        prefix config;
        revision-date 2013-04-05;
    }

    import opendaylight-md-sal-binding {
        prefix mdsal;
        revision-date 2013-10-28;
    }

    import fast-system {
        prefix fast-system;
        revision-date 2015-12-17;
    }

    description
        "A new FAST application";

    revision "2016-09-02" {
        description
            "Initial revision";
    }

    identity fast-app-scheduling {
        base config:module-type;
        config:java-name-prefix Scheduling;
    }

    augment "/config:modules/config:module/config:configuration" {
        case fast-app-scheduling {
            when "/config:modules/config:module/config:type = 'fast-app-scheduling'";
            container fast-system {
                uses config:service-ref {
                    refine type {
                        mandatory true;
                        config:required-identity fast-system:fast-system;
                    }
                }
            }

            container broker {
                uses config:service-ref {
                    refine type {
                        mandatory true;
                        config:required-identity mdsal:binding-broker-osgi-registry;
                    }
                }
            }
        }
    }
}
