module fast-app-scheduling {
    yang-version 1;
    namespace "urn:fast:app:scheduling";
    prefix "fast-app-scheduling";
    
    import ietf-inet-types {
    	prefix inet;
    }

    revision "2016-09-02" {
        description "Initial revision of the FAST application scheduling API";
    }
    
    container flow-set-path{
	    list flow-path{
	    	key id;
	    	leaf id{
	    		type string;
	    	}
	    	container flow-spec{
	    		leaf src-ip{
		    		type string;
		    	}
		    	leaf dst-ip{
		    		type string;
		   		}
		    	leaf src-port{
		    		type string;
		   		}
		    	leaf dst-port{
		    		type string;
		   		}
		    	leaf protocol{
		    		type string;
		   		}
	   		}
	  		container path {
		  		list link-spec{
		   			key link-id;
		    		leaf link-id{
		    			type string;
		   			}
		   			leaf source{
		   				type string;
		   			}
		   			leaf destination{
		   				type string;
		   			}
				}
	  		}	
	    }
    }
    
    
}
